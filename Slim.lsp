(defun c:LoadMyVBAs()
  (vl-vbaload "F:/Gaurav/civil3D/DrawEquation.dvb")
  (vl-vbaload "F:/Gaurav/civil3D/Area_multiple.dvb")
  )
(defun c:SlimLayers()
  (vl-vbarun "SlimLayers")
  )
(defun c:DrawEquation()
  (vl-vbarun "drawEquation")
  )
(defun c:scaleLine()
  (vl-vbarun "scaleLine")
  )

(defun c:NewElevation()
  (vl-vbarun "Elevation")	
)

(defun c:ExElevation()
  (vl-vbarun "Elevation_ExistingBlock")
  )

(defun c:HatchAll()
  (vl-vbarun "HatchAll")
  )
(defun c:Cross()
  (vl-vbarun "cross")
  )
(defun c:RED()
  (vl-vbarun "Red")
  )
(defun c:OverRideDIM()
  (vl-vbarun "OverRideDIM")
    )
(defun c:SPattern()
  (vl-vbarun "DrawSlopePattern")
    )
(defun c:isclosed()
  (vl-vbarun "isclosed")
    )

(defun c:Hmove()
  (vl-vbarun "Hmove")
    )

(defun c:Vmove()
  (vl-vbarun "Vmove")
    )

(defun c:Zmove()
  (vl-vbarun "Zmove")
    )
(defun c:Pclose ( / e i s x etdata)
    (if (setq s (ssget))
        (progn
            (setq i 0)
            (repeat (sslength s)
                (setq e (ssname s i)
                      x (cdr (assoc 0 (entget e)))
                      i (1+ i)
                )
	      (setq etdata (entget e))
	      (entmod (subst '(70 . 129) (assoc 70 etdata) etdata))
            )
        )
    )
    (princ)
)
